AUTO-DISCOVERY-MIB DEFINITIONS ::= BEGIN

IMPORTS
    MODULE-IDENTITY,
    OBJECT-TYPE,
    Integer32,
    Gauge32,
    TimeTicks,
    IpAddress,
    enterprises,
    NOTIFICATION-TYPE
        FROM SNMPv2-SMI
    MODULE-COMPLIANCE,
    OBJECT-GROUP,
    NOTIFICATION-GROUP
        FROM SNMPv2-CONF;

-- Identificacao do modulo
autoDiscoveryMib MODULE-IDENTITY
    LAST-UPDATED "202312100000Z"
    ORGANIZATION "Organizacao do Jones"
    CONTACT-INFO "Contato do Jones"
    DESCRIPTION "MIB para representar informacoes de autodescoberta"
    REVISION "202312100000Z"
    DESCRIPTION "Primeira revisao"
    ::= { enterprises 1 }

-- Definicao de objetos
autoDiscoveryObjects OBJECT IDENTIFIER ::= { autoDiscoveryMib 1 }
autoDiscoveryExperimental OBJECT IDENTIFIER ::= { autoDiscoveryObjects 1 }

-- Objetos individuais
autoDiscoveryIP OBJECT-TYPE
    SYNTAX IpAddress
    MAX-ACCESS read-only
    STATUS current
    DESCRIPTION "Endereco IP do dispositivo"
    ::= { autoDiscoveryExperimental 3 }

autoDiscoveryMAC OBJECT-TYPE
    SYNTAX OCTET STRING
    MAX-ACCESS read-only
    STATUS current
    DESCRIPTION "Endereco MAC do dispositivo"
    ::= { autoDiscoveryExperimental 4 }

autoDiscoveryOnline OBJECT-TYPE
    SYNTAX INTEGER { online(1), offline(2) }
    MAX-ACCESS read-only
    STATUS current
    DESCRIPTION "Estado online do dispositivo (1 - online, 2 - offline)"
    ::= { autoDiscoveryExperimental 5 }

autoDiscoveryFabricante OBJECT-TYPE
    SYNTAX OCTET STRING
    MAX-ACCESS read-only
    STATUS current
    DESCRIPTION "Fabricante do dispositivo"
    ::= { autoDiscoveryExperimental 6 }

autoDiscoveryTotalDispositivos OBJECT-TYPE
    SYNTAX Integer32
    MAX-ACCESS read-only
    STATUS current
    DESCRIPTION "Total de dispositivos descobertos"
    ::= { autoDiscoveryExperimental 7 }

-- Adicionando uma tabela para representar dispositivos descobertos
autoDiscoveryTable OBJECT-TYPE
    SYNTAX SEQUENCE OF AutoDiscoveryEntry
    MAX-ACCESS not-accessible
    STATUS current
    DESCRIPTION "Tabela de dispositivos descobertos"
    ::= { autoDiscoveryExperimental 8 }

autoDiscoveryEntry OBJECT-TYPE
    SYNTAX AutoDiscoveryEntry
    MAX-ACCESS not-accessible
    STATUS current
    DESCRIPTION "Entrada da tabela de dispositivos descobertos"
    INDEX { autoDiscoveryMainTableIndex }
    ::= { autoDiscoveryTable 1 }

autoDiscoveryMainTableIndex OBJECT-TYPE
    SYNTAX INTEGER (1..2147483647)
    MAX-ACCESS not-accessible
    STATUS current
    DESCRIPTION "Indice da entrada na tabela de dispositivos descobertos"
    ::= { autoDiscoveryEntry 1 }

-- Novo objeto para atender a TYPE write-only
autoDiscoveryWriteOnly OBJECT-TYPE
    SYNTAX INTEGER
    MAX-ACCESS read-write
    STATUS current
    DESCRIPTION "Objeto de exemplo marcado como write-only"
    ::= { autoDiscoveryExperimental 9 }

-- Novo objeto para atender a TYPE read-write
autoDiscoveryReadWrite OBJECT-TYPE
    SYNTAX INTEGER
    MAX-ACCESS read-write
    STATUS current
    DESCRIPTION "Objeto de exemplo marcado como read-write"
    ::= { autoDiscoveryExperimental 10 }

-- Novo objeto para atender a STATUS optional
autoDiscoveryOptional OBJECT-TYPE
    SYNTAX INTEGER
    MAX-ACCESS read-only
    STATUS deprecated
    DESCRIPTION "Objeto de exemplo marcado como optional"
    ::= { autoDiscoveryExperimental 11 }

AutoDiscoveryEntry ::= SEQUENCE {
    autoDiscoveryMainTableIndex INTEGER,
    autoDiscoveryEntryIPAddress IpAddress,
    autoDiscoveryEntryMAC OCTET STRING,
    autoDiscoveryEntryOnline INTEGER,
    autoDiscoveryEntryFabricante OCTET STRING,
    autoDiscoveryPrimeiraDescoberta TimeTicks
}

autoDiscoveryEntryIndex OBJECT-TYPE
    SYNTAX INTEGER (1..2147483647)
    MAX-ACCESS not-accessible
    STATUS current
    DESCRIPTION "Indice da entrada na tabela de dispositivos descobertos"
    ::= { autoDiscoveryEntry 1 }

autoDiscoveryEntryIPAddress OBJECT-TYPE
    SYNTAX IpAddress
    MAX-ACCESS read-only
    STATUS current
    DESCRIPTION "Endereco IP do dispositivo na tabela"
    ::= { autoDiscoveryEntry 2 }

autoDiscoveryEntryMAC OBJECT-TYPE
    SYNTAX OCTET STRING
    MAX-ACCESS read-only
    STATUS current
    DESCRIPTION "Endereco MAC do dispositivo na tabela"
    ::= { autoDiscoveryEntry 3 }

autoDiscoveryEntryOnline OBJECT-TYPE
    SYNTAX INTEGER { online(1), offline(2) }
    MAX-ACCESS read-only
    STATUS current
    DESCRIPTION "Estado online do dispositivo na tabela (1 - online, 2 - offline)"
    ::= { autoDiscoveryEntry 4 }

autoDiscoveryEntryFabricante OBJECT-TYPE
    SYNTAX OCTET STRING
    MAX-ACCESS read-only
    STATUS current
    DESCRIPTION "Fabricante do dispositivo na tabela"
    ::= { autoDiscoveryEntry 5 }

autoDiscoveryPrimeiraDescoberta OBJECT-TYPE
    SYNTAX TimeTicks
    MAX-ACCESS read-only
    STATUS current
    DESCRIPTION "Tempo desde a primeira descoberta"
    ::= { autoDiscoveryEntry 6 }

END
