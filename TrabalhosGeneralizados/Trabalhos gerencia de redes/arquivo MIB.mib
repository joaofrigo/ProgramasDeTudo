AUTO-DISCOVERY-MIB DEFINITIONS ::= BEGIN

IMPORTS
    MODULE-IDENTITY,
    OBJECT-TYPE,
    Integer32,
    Gauge32,
    TimeTicks,
    IpAddress,
    enterprises,
    NOTIFICATION-TYPE
        FROM SNMPv2-SMI
    MODULE-COMPLIANCE,
    OBJECT-GROUP,
    NOTIFICATION-GROUP
        FROM SNMPv2-CONF;

-- Identificacao do modulo
autoDiscoveryMib MODULE-IDENTITY
    LAST-UPDATED "202312100000Z"
    ORGANIZATION "Organizacao do Jones"
    CONTACT-INFO "Contato do Jones"
    DESCRIPTION "MIB para representar informacoes de autodescoberta"
    REVISION "202312100000Z"
    DESCRIPTION "Primeira revisao"
    ::= { enterprises 1 }

-- Definicao de objetos
autoDiscoveryObjects OBJECT IDENTIFIER ::= { autoDiscoveryMib 1 }

-- Objetos individuais, primeiro criamos as informacoes mais basicas que adquirimos com a auto descoberta
autoDiscoveryIP OBJECT-TYPE
    SYNTAX IpAddress
    MAX-ACCESS read-only
    STATUS current
    DESCRIPTION "Endereco IP do dispositivo"
    ::= { autoDiscoveryObjects 1 }

autoDiscoveryMAC OBJECT-TYPE
    SYNTAX OCTET STRING
    MAX-ACCESS read-only
    STATUS current
    DESCRIPTION "Endereco MAC do dispositivo"
    ::= { autoDiscoveryObjects 2 }

autoDiscoveryOnline OBJECT-TYPE
    SYNTAX INTEGER { online(1), offline(2) }
    MAX-ACCESS read-only
    STATUS current
    DESCRIPTION "Estado online do dispositivo (1 - online, 2 - offline)"
    ::= { autoDiscoveryObjects 3 }

autoDiscoveryFabricante OBJECT-TYPE
    SYNTAX OCTET STRING
    MAX-ACCESS read-only
    STATUS current
    DESCRIPTION "Fabricante do dispositivo"
    ::= { autoDiscoveryObjects 4 }

autoDiscoveryTotalDispositivos OBJECT-TYPE
    SYNTAX Integer32
    MAX-ACCESS read-only
    STATUS current
    DESCRIPTION "Total de dispositivos descobertos"
    ::= { autoDiscoveryObjects 5 }

-- Agora comecamos a preencher as necessidades do que foi pedido
autoDiscoveryTable OBJECT-TYPE
    SYNTAX SEQUENCE OF AutoDiscoveryEntry
    MAX-ACCESS not-accessible
    STATUS current
    DESCRIPTION "Tabela de dispositivos descobertos"
    ::= { autoDiscoveryObjects 6 }

autoDiscoveryEntry OBJECT-TYPE
    SYNTAX AutoDiscoveryEntry
    MAX-ACCESS not-accessible
    STATUS current
    DESCRIPTION "Entrada da tabela de dispositivos descobertos"
    INDEX { autoDiscoveryEntryIndex }
    ::= { autoDiscoveryTable 1 }

autoDiscoveryEntryIndex OBJECT-TYPE
    SYNTAX INTEGER (1..2147483647)
    MAX-ACCESS not-accessible
    STATUS current
    DESCRIPTION "Indice da entrada na tabela de dispositivos descobertos"
    ::= { autoDiscoveryEntry 1 }


AutoDiscoveryEntry ::= SEQUENCE {
    autoDiscoveryEntryIndex INTEGER,
    autoDiscoveryEntryIP IpAddress,
    autoDiscoveryEntryMAC OCTET STRING,
    autoDiscoveryEntryOnline INTEGER,
    autoDiscoveryEntryFabricante OCTET STRING
}

autoDiscoveryEntryIP OBJECT-TYPE
    SYNTAX IpAddress
    MAX-ACCESS read-only
    STATUS current
    DESCRIPTION "Endereco IP do dispositivo na tabela"
    ::= { autoDiscoveryEntry 2 }

autoDiscoveryEntryMAC OBJECT-TYPE
    SYNTAX OCTET STRING
    MAX-ACCESS read-only
    STATUS current
    DESCRIPTION "Endereco MAC do dispositivo na tabela"
    ::= { autoDiscoveryEntry 3 }

autoDiscoveryEntryOnline OBJECT-TYPE
    SYNTAX INTEGER { online(1), offline(2) }
    MAX-ACCESS read-only
    STATUS current
    DESCRIPTION "Estado online do dispositivo na tabela (1 - online, 2 - offline)"
    ::= { autoDiscoveryEntry 4 }

autoDiscoveryEntryFabricante OBJECT-TYPE
    SYNTAX OCTET STRING
    MAX-ACCESS read-only
    STATUS current
    DESCRIPTION "Fabricante do dispositivo na tabela"
    ::= { autoDiscoveryEntry 5 }

END
